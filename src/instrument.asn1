Instrument { } DEFINITIONS AUTOMATIC TAGS ::=

BEGIN

IMPORTS
	CCY FROM Iso4217
	Resource FROM Resources;

	MONETARY ::= REAL

	-- everything we need to uniquely identify an instrument
	-- regard these as references, they can be searched using cmd 42xx
	Ident ::= SEQUENCE {
		name VisibleString(SIZE(1..32)),
		cfi PrintableString(SIZE(6)),
		opol PrintableString(SIZE(4)) OPTIONAL,
		-- ordinary isin
		isin PrintableString(SIZE(12)) OPTIONAL,
		-- for yank securities
		cusip PrintableString OPTIONAL,
		-- for pommie securities
		sedol PrintableString OPTIONAL,
		-- reuters
		ric PrintableString(SIZE(5)) OPTIONAL,
		-- bloomberg
		bbg PrintableString(SIZE(4)) OPTIONAL,
		-- ourselves
		gaid INTEGER
	}

	DeliverySched ::= SEQUENCE {
		issue GeneralizedTime,
		expiry GeneralizedTime,
		settle GeneralizedTime
	}

	RIGHT ::= ENUMERATED {
		put,
		call
	}

	CashFlow ::= SEQUENCE {
		from InstrumentRef,
		to InstrumentRef
	}

	Option ::= SEQUENCE {
		deliv-sched DeliverySched,
		strike MONETARY,
		ratio REAL,
		underlyer Ident,
		right RIGHT,
		buy-flow CashFlow,
		exer-flow CashFlow
	}

	Cash ::= SEQUENCE {
		currency CCY
	}

	FX ::= SEQUENCE {
		term-flow CashFlow
	}

	-- the union over all instruments
	Instance ::= CHOICE {
		option Option,
		cash Cash,
		fx FX
	}

	Instrument ::= SEQUENCE {
		ident Ident,
		instance Instance,
		urns SEQUENCE OF Resource
	}

	-- in awe of a lack of by-ref serialisation
	InstrumentRef ::= CHOICE {
		instr Instrument,
		ident Ident
	}

	-- strange construction
	OptionChain ::= SEQUENCE {
		ref-instr InstrumentRef,
		-- chain of strike prices
		chain SEQUENCE OF MONETARY,
		-- we assume the same ratio everywhere
		ratio REAL
		-- and both rights
	}

END


Resources DEFINITIONS ::=
BEGIN
	ResourceType ::= ENUMERATED {
		tseries,
		ticker-plant,
		nresource-types
	}

	Resource ::= SEQUENCE {
		type ResourceType
	}
END


Iso4217 DEFINITIONS ::=
BEGIN
	CCY ::= ENUMERATED {
		eur (48),
		usd (149),
		gbp (51),
		cad (26),
		aud (7),
		nzd (110),
		krw (78),
		jpy (72),
		inr (66),
		hkd (59),
		cny (33),
		rub (122),
		sek (128),
		nok (108),
		dkk (41),
		isk (69),
		eek (44),
		huf (63),
		mxn (101),
		brl (20),
		clp (32),
		chf (29),
		-- precious metals as defined by 4217
		xau (154),
		xag (153),
		xpt (165)
	}
END
